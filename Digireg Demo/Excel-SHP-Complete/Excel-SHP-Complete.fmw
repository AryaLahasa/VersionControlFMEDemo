FME workspace Excel-SHP-Complete.fmw

Parameters:
- SourceDataset_XLSXR = $(FME_MF_DIR)Startup Data Jakarta.xlsx   # Source Microsoft Excel File(s)
- DestDataset_FILEGDB = D:\LAHASA\Case Study - Startup Jakarta\RESULTS   # File Geodatabase
- DestDataset_XLSXW = D:\LAHASA\Case Study - Startup Jakarta\Startup Data Jakarta_update.xlsx   # Destination Microsoft Excel File

Readers:
- XLSXR_1: XLSXR from $(SourceDataset_XLSXR)

Writers:
- FILEGDB_1: FILEGDB to $(DestDataset_FILEGDB)
- XLSXW_1: XLSXW to $(DestDataset_XLSXW)

Note: Excel Data
Startup Jakarta (reader XLSXR_1)
    attributes: Company Name char(40), Founded Date char(11), Address char(239), Type char(8), Slipicon? char(4), Longitude x_coordinate, Latitude y_coordinate
    -> Tester
Note: Filtering out empty data
Tester
    BOOL_OP = AND
    TEST_CLAUSE:
      TEST Latitude ATTRIBUTE_HAS_A_VALUE ""
      TEST Longitude ATTRIBUTE_HAS_A_VALUE ""
    TEST_MODE = TEST
    PASSED -> Geocoder
Note: Geocoder [safe.geocoder.Geocoder] / Service: / Geocoding Service: OpenStreetMap / Connection: / Nominatim URL: https://nominatim.openstreetmap.org/ / Geocoding Parameters: / Mode: Reverse / Latitude: @Value(Latitude) / Longitude: @Value(Longitude) / Advanced: / Timeout (s): 60 / Maximum Concurrent Requests: 4 / Include Full JSON Response: No / Verify HTTPS Certificates: Yes
Geocoder
    GEOCODING_SERVICE = OpenStreetMap
    RETURN_JSON_RESPONSE = no
    THREADS = 4
    TIMEOUT = 60
    VERIFY_HTTPS = yes
    -> AttributeManager
Note: Cleaning and setting its attributes
AttributeManager
    ATTR_TABLE:
      RENAME_SET_VALUE Company Name > Nama Perusahaan (varchar(40))
      RENAME_SET_VALUE Founded Date > Tanggal Didirikan (varchar(11))
      RENAME_SET_VALUE Address > Alamat (varchar(200)) = @Value(_address)
      RENAME_SET_VALUE Type > Tipe (varchar(8))
      RENAME_SET_VALUE Slipicon? > Slipicon (varchar(4))
      SET_TO Longitude (buffer) = @Value(_longitude)
      SET_TO Latitude (varchar(200)) = @Value(_latitude)
      REMOVE _address (varchar(200))
      REMOVE _latitude (varchar(200))
      REMOVE _longitude (buffer)
    -> StartUp_Jakarta (writer FILEGDB_1)
    -> Sheet1 (writer XLSXW_1)
Note: GDB
StartUp_Jakarta (writer FILEGDB_1)
    attributes: Nama_Perusahaan text(40), Tanggal_Didirikan text(11), Alamat text(239), Tipe text(8), Slipicon text(4), Longitude double, Latitude double
Sheet1 (writer XLSXW_1)
    attributes: Nama Perusahaan string(40), Tanggal Didirikan string(11), Alamat string(239), Tipe string(8), Slipicon string(4), Longitude number(20), Latitude number(20)
