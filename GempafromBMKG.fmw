FME workspace GempafromBMKG.fmw

Parameters:
- DestDataset_SHAPEFILE = D:\LAHASA\Case Study - BMKG Data   # Destination Esri Shapefile Folder

Writers:
- SHAPEFILE_1: SHAPEFILE to $(DestDataset_SHAPEFILE)

Bookmark: Trigger
Creator
    GEOMTYPE = Geometry Object
    NUM = 1
    CREATED -> JSONFragmenter

Bookmark: Extract data from API
JSONFragmenter
    EXPLODE_FORMAT = JSON
    EXTRACT_ATTR = Yes
    FILEPATH_OR_URL = https://data.bmkg.go.id/DataMKG/TEWS/gempadirasakan.json
    JSON_QUERY = json[*]
    NEW_ATTRIBUTES = Coordinates
    READ_FROM_FILE = YES
    RECURSIVE = Yes
    REJECT_EMPTY_LISTS = YES
    RESULT_ATTRIBUTE = _result
    FRAGMENTS -> JSONFormatter
JSONFormatter
    ERROR_LIST_ATTR = _json_error
    FORMAT = Pretty Print
    INDENT_STYLE = 3 spaces
    JSON_DOCUMENT = @Value(_result)
    OUTPUT_ATTR = _formatted
    OUTPUT_ENCODING = UTF-8
    READ_FROM_FILE = NO
    REMOVE_EMPTY_OBJECTS_AND_ARRAYS = No
    REMOVE_EMPTY_STRINGS = No
    REMOVE_NULLS = No
    -> AttributeExposer
AttributeExposer
    ATTR_LIST = gempa{},gempa{}.Coordinates,gempa{}.Wilayah,gempa{}.DateTime,gempa{}.Dirasakan,gempa{}.Magnitude,gempa{}.Jam
    -> ListExploder
ListExploder
    ATTR_ACCUM_MODE = Prefix List Attributes
    INCOMING_PREFIX = _
    INDEX_ATTR = _element_index
    LIST_ATTR = gempa{}
    ELEMENTS -> SubstringExtractor

Bookmark: Cleaning Data
SubstringExtractor
    END = 4
    RESULT_ATTR = Y
    SRC_STRING = @Value(_Coordinates)
    START = 0
    -> SubstringExtractor_2
SubstringExtractor_2
    END = -1
    RESULT_ATTR = X
    SRC_STRING = @Value(_Coordinates)
    START = 5
    -> StringReplacer
StringReplacer
    CASE = NO
    FIND_TEXT = ,
    NO_MATCH = _FME_NO_OP_
    REGEXP = NO
    SRC_ATTRS = X,Y
    -> StringReplacer_2
StringReplacer_2
    CASE = NO
    FIND_TEXT = .
    NO_MATCH = _FME_NO_OP_
    REGEXP = NO
    REPLACE_TEXT = ,
    SRC_ATTRS = X,Y
    -> VertexCreator
VertexCreator
    MEASURE_TYPE = Continuous
    MODE_NAME = Replace with Point
    XVAL = @Value(X)
    YVAL = @Value(Y)
    -> Reprojector
Reprojector
    DEST = LL-WGS84
    INTERPOLATION_TYPE_NAME = Nearest Neighbor
    RASTER_CELL_SIZE = Preserve Cells
    RASTER_TOLERANCE = 0.0
    REPROJECTED -> AttributeManager
AttributeManager
    ATTR_TABLE:
      REMOVE Coordinates (buffer)
      RENAME_SET_VALUE _result > Hasil (varchar(200))
      REMOVE _gempa (varchar(200))
      RENAME_SET_VALUE _Wilayah > Wilayah (varchar(200))
      RENAME_SET_VALUE _DateTime > DateTime (varchar(200))
      RENAME_SET_VALUE _Dirasakan > Dirasakan (varchar(200))
      RENAME_SET_VALUE _Magnitude > Magnitude (varchar(200))
      RENAME_SET_VALUE _Jam > Jam (varchar(200))
      REMOVE _element_index (uint32)
      RENAME_SET_VALUE _Coordinates > Coordinates (buffer)
      REMOVE _formatted (buffer)
      REMOVE json_type (buffer)
      REMOVE json_index (uint32)
      REMOVE _creation_instance (uint64)
    -> GempaBMKG (writer SHAPEFILE_1)

Bookmark: SHP OUTPUT
GempaBMKG (writer SHAPEFILE_1)
    attributes: Hasil varchar(200), Wilayah varchar(200), DateTime varchar(200), Dirasakan varchar(200), Magnitude varchar(200), Jam varchar(200), Coordinate varchar(200), Y varchar(254), X varchar(254)
